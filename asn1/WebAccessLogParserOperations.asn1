-- Copyright 2009 Google Inc.
-- Author: Romain Lenglet <romain.lenglet@berabera.info>
--
-- Licensed under the Apache License, Version 2.0 (the "License");
-- you may not use this file except in compliance with the License.
-- You may obtain a copy of the License at
--
--     http://www.apache.org/licenses/LICENSE-2.0
--
-- Unless required by applicable law or agreed to in writing, software
-- distributed under the License is distributed on an "AS IS" BASIS,
-- WITHOUT WARRANTIES OR CONDITIONS OF ANY KIND, either express or implied.
-- See the License for the specific language governing permissions and
-- limitations under the License.

-- ASN.1 definitions for the PDUs used to interact with a web access
-- log parser.

WebAccessLogParserOperations DEFINITIONS IMPLICIT TAGS ::=
BEGIN

IMPORTS
    LogEntry FROM WebAccessLog;

-- Simplified PDU definitions that are inspired by those of ROSE's
-- Invoke, ReturnResult, and ReturnError PDUs, as defined in the
-- Remote-Operations-Generic-ROS-PDUs module in ITU-T X.880:07 (1994)
-- Amend. 1 (11/1995):

-- Operation to request to the parser to parse a log file:
ParseLogFile ::= SEQUENCE {  -- Invoke
  invoke-id INTEGER,
  argument UTF8String  -- the name of the file to parse
}

-- Error result of a ParseLogFile operation:
CannotOpenFile ::= SEQUENCE {  -- ReturnError
  invoke-id INTEGER
}

-- Operation (linked reply to ParseLogFile) to send one log entry to
-- the client:
ReturnLogEntry ::= SEQUENCE {  -- Invoke
  linked-id INTEGER,  -- matches the linked-id passed in a ParseLogFile
  argument LogEntry
}

EndOfFile ::= SEQUENCE {  -- ReturnResult
  invoke-id INTEGER
}

-- PDUs sent by clients to the parser:
ConsumerPDU ::= CHOICE {
  parse-log-file [1] ParseLogFile,
  ...
}

-- PDUs sent by the parser to clients:
SupplierPDU ::= CHOICE {
  cannot-open-file [1] CannotOpenFile,
  return-log-entry [2] ReturnLogEntry,
  end-of-file      [3] EndOfFile,
  ...
}

END
